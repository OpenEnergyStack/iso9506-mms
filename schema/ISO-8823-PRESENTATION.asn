-- Module ISO8823-PRESENTATION (X.226:07/1994)
-- Modified for compatibility with rasn-compiler

ISO8823-PRESENTATION
DEFINITIONS ::= BEGIN

-- Set to NULL to eliminate dependency on Reliable-Transfer-APDU module
RTORQapdu ::= NULL
RTOACapdu ::= NULL
RTORJapdu ::= NULL
RTABapdu ::= NULL

-- Productions

Simply-encoded-data ::= OCTET STRING

Transfer-syntax-name ::= OBJECT IDENTIFIER

Presentation-context-identifier ::= INTEGER

PDV-list ::= SEQUENCE {
   transfer-syntax-name Transfer-syntax-name OPTIONAL,
   presentation-context-identifier Presentation-context-identifier,
   presentation-data-values CHOICE {
      single-ASN1-type [0] EXPLICIT EXTERNAL, -- Originally ABSTRACT-SYNTAX.&Type
      octet-aligned [1] IMPLICIT OCTET STRING,
      arbitrary [2] IMPLICIT BIT STRING
   }
}

Fully-encoded-data ::= SEQUENCE OF PDV-list

User-data ::= CHOICE {
   simply-encoded-data [APPLICATION 0] IMPLICIT Simply-encoded-data,
   fully-encoded-data [APPLICATION 1] IMPLICIT Fully-encoded-data,
   ...
}

CPC-type ::= User-data

Abort-reason ::= INTEGER {
   reason-not-specified(0),
   unrecognized-ppdu(1),
   unexpected-ppdu(2),
   unexpected-session-service-primitive(3),
   unrecognized-ppdu-parameter(4),
   unexpected-ppdu-parameter(5),
   invalid-ppdu-parameter-value(6)
}

Abstract-syntax-name ::= OBJECT IDENTIFIER

Presentation-selector ::= OCTET STRING

Called-presentation-selector ::= Presentation-selector

Calling-presentation-selector ::= Presentation-selector

Result ::= INTEGER {
   acceptance(0),
   user-rejection(1),
   provider-rejection(2)
}

Default-context-result ::= Result

Event-identifier ::= INTEGER {
   cp-PPDU(0),
   cpa-PPDU(1),
   cpr-PPDU(2),
   aru-PPDU(3),
   arp-PPDU(4),
   ac-PPDU(5),
   aca-PPDU(6),
   td-PPDU(7),
   ttd-PPDU(8),
   te-PPDU(9),
   tc-PPDU(10),
   tcc-PPDU(11),
   rs-PPDU(12),
   rsa-PPDU(13),
   s-release-indication(14),
   s-release-confirm(15),
   s-token-give-indication(16),
   s-token-please-indication(17),
   s-control-give-indication(18),
   s-sync-minor-indication(19),
   s-sync-minor-confirm(20),
   s-sync-major-indication(21),
   s-sync-major-confirm(22),
   s-p-exception-report-indication(23),
   s-u-exception-report-indication(24),
   s-activity-start-indication(25),
   s-activity-resume-indication(26),
   s-activity-interrupt-indication(27),
   s-activity-interrupt-confirm(28),
   s-activity-discard-indication(29),
   s-activity-discard-confirm(30),
   s-activity-end-indication(31),
   s-activity-end-confirm(32)
}

Context-list ::= SEQUENCE OF SEQUENCE {
   presentation-context-identifier Presentation-context-identifier,
   abstract-syntax-name Abstract-syntax-name,
   transfer-syntax-name-list SEQUENCE OF Transfer-syntax-name
}

Presentation-context-addition-list ::= Context-list

Result-list ::= SEQUENCE OF SEQUENCE {
   result [0] IMPLICIT Result,
   transfer-syntax-name [1] IMPLICIT Transfer-syntax-name OPTIONAL,
   provider-reason [2] IMPLICIT INTEGER {
      reason-not-specified(0),
      abstract-syntax-not-supported(1),
      proposed-transfer-syntaxes-not-supported(2),
      local-limit-on-DCS-exceeded(3)
   } OPTIONAL
}

Presentation-context-addition-result-list ::= Result-list

Presentation-context-definition-list ::= Context-list

Presentation-context-definition-result-list ::= Result-list

Presentation-requirements ::= BIT STRING {
   context-management(0),
   restoration(1)
}

Protocol-options ::= BIT STRING {
   nominated-context(0),
   short-encoding(1),
   packed-encoding-rules(2)
}

Protocol-version ::= BIT STRING {
   version-1(0)
}

Provider-reason ::= INTEGER {
   reason-not-specified(0),
   temporary-congestion(1),
   local-limit-exceeded(2),
   called-presentation-address-unknown(3),
   protocol-version-not-supported(4),
   default-context-not-supported(5),
   user-data-not-readable(6),
   no-PSAP-available(7)
}

Responding-presentation-selector ::= Presentation-selector

User-session-requirements ::= BIT STRING {
   half-duplex(0),
   duplex(1),
   expedited-data(2),
   minor-synchronize(3),
   major-synchronize(4),
   resynchronize(5),
   activity-management(6),
   negotiated-release(7),
   capability-data(8),
   exceptions(9),
   typed-data(10),
   symmetric-synchronize(11),
   data-separation(12)
}

Mode-selector ::= SET {
   mode-value [0] IMPLICIT INTEGER {
      x410-1984-mode(0),
      normal-mode(1)
   }
}

Default-context-name ::= SEQUENCE {
   abstract-syntax-name [0] IMPLICIT Abstract-syntax-name,
   transfer-syntax-name [1] IMPLICIT Transfer-syntax-name
}

CP-PPDU ::= SET {
   mode-selector [0] IMPLICIT Mode-selector,
   x410-mode-parameters [1] IMPLICIT RTORQapdu OPTIONAL,
   normal-mode-parameters [2] IMPLICIT SEQUENCE {
      protocol-version [0] IMPLICIT Protocol-version OPTIONAL,
      calling-presentation-selector [1] IMPLICIT Calling-presentation-selector OPTIONAL,
      called-presentation-selector [2] IMPLICIT Called-presentation-selector OPTIONAL,
      presentation-context-definition-list [4] IMPLICIT Presentation-context-definition-list OPTIONAL,
      default-context-name [6] IMPLICIT Default-context-name OPTIONAL,
      presentation-requirements [8] IMPLICIT Presentation-requirements OPTIONAL,
      user-session-requirements [9] IMPLICIT User-session-requirements OPTIONAL,
      protocol-options [11] Protocol-options OPTIONAL,
      initiators-nominated-context [12] Presentation-context-identifier OPTIONAL,
      extensions [14] SEQUENCE {
         ...
      } OPTIONAL,
      user-data User-data OPTIONAL
   } OPTIONAL
}

CPA-PPDU ::= SET {
   mode-selector [0] IMPLICIT Mode-selector,
   x410-mode-parameters [1] IMPLICIT RTOACapdu OPTIONAL,
   normal-mode-parameters [2] IMPLICIT SEQUENCE {
      protocol-version [0] IMPLICIT Protocol-version OPTIONAL,
      responding-presentation-selector [3] IMPLICIT Responding-presentation-selector OPTIONAL,
      presentation-context-definition-result-list [5] IMPLICIT Presentation-context-definition-result-list OPTIONAL,
      presentation-requirements [8] IMPLICIT Presentation-requirements OPTIONAL,
      user-session-requirements [9] IMPLICIT User-session-requirements OPTIONAL,
      protocol-options [11] Protocol-options OPTIONAL,
      responders-nominated-context [13] Presentation-context-identifier OPTIONAL,
      user-data User-data OPTIONAL
   } OPTIONAL
}

CPR-PPDU ::= CHOICE {
   x400-mode-parameters RTORJapdu,
   normal-mode-parameters SEQUENCE {
      protocol-version [0] IMPLICIT Protocol-version OPTIONAL,
      responding-presentation-selector [3] IMPLICIT Responding-presentation-selector OPTIONAL,
      presentation-context-definition-result-list [5] IMPLICIT Presentation-context-definition-result-list OPTIONAL,
      default-context-result [7] IMPLICIT Default-context-result OPTIONAL,
      provider-reason [10] IMPLICIT Provider-reason OPTIONAL,
      user-data User-data OPTIONAL
   }
}

Presentation-context-identifier-list ::= SEQUENCE OF SEQUENCE {
   presentation-context-identifier Presentation-context-identifier,
   transfer-syntax-name Transfer-syntax-name
}

ARU-PPDU ::= CHOICE {
   x400-mode-parameters RTABapdu,
   normal-mode-parameters [0] IMPLICIT SEQUENCE {
      presentation-context-identifier-list [0] IMPLICIT Presentation-context-identifier-list OPTIONAL,
      user-data User-data OPTIONAL
   }
}

ARP-PPDU ::= SEQUENCE {
   provider-reason [0] IMPLICIT Abort-reason OPTIONAL,
   event-identifier [1] IMPLICIT Event-identifier OPTIONAL
}

Abort-type ::= CHOICE {
   aru-ppdu ARU-PPDU,
   arp-ppdu ARP-PPDU
}

Presentation-context-deletion-list ::= SEQUENCE OF Presentation-context-identifier

AC-PPDU ::= SEQUENCE {
   presentation-context-addition-list [0] IMPLICIT Presentation-context-addition-list OPTIONAL,
   presentation-context-deletion-list [1] IMPLICIT Presentation-context-deletion-list OPTIONAL,
   user-data User-data OPTIONAL
}

Presentation-context-deletion-result-list ::= SEQUENCE OF INTEGER {
   acceptance(0),
   user-rejection(1)
}

ACA-PPDU ::= SEQUENCE {
   presentation-context-addition-result-list [0] IMPLICIT Presentation-context-addition-result-list OPTIONAL,
   presentation-context-deletion-result-list [1] IMPLICIT Presentation-context-deletion-result-list OPTIONAL,
   user-data User-data OPTIONAL
}

Typed-data-type ::= CHOICE {
   acPPDU [0] IMPLICIT AC-PPDU,
   acaPPDU [1] IMPLICIT ACA-PPDU,
   ttdPPDU User-data
}

RS-PPDU ::= SEQUENCE {
   presentation-context-identifier-list [0] IMPLICIT Presentation-context-identifier-list OPTIONAL,
   user-data User-data OPTIONAL
}

RSA-PPDU ::= SEQUENCE {
   presentation-context-identifier-list [0] IMPLICIT Presentation-context-identifier-list OPTIONAL,
   user-data User-data OPTIONAL
}

END
