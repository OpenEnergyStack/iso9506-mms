-- Modified for compatibility with rasn-compiler

ISO-9506-MMS-1
{ iso standard 9506 part(2) mms-abstract-syntax-version1(1) }
DEFINITIONS ::= BEGIN

IMPORTS
   ApplicationReference
FROM MMS-Environment-1 { iso standard 9506 part(2) mms-environment-version1 (4) }

   ObtainFile-Request,
   ObtainFile-Response,
   ObtainFile-Error,
   FileOpen-Request,
   FileOpen-Response,
   FileRead-Request,
   FileRead-Response,
   FileClose-Request,
   FileClose-Response,
   FileRename-Request,
   FileRename-Response,
   FileRename-Error,
   FileDelete-Request,
   FileDelete-Response,
   FileDirectory-Request,
   FileDirectory-Response,
   DefineScatteredAccess-Request,
   DefineScatteredAccess-Response,
   ScatteredAccessDescription,
   GetScatteredAccessAttributes-Request,
   GetScatteredAccessAttributes-Response
FROM ISO-9506-MMS-1A { iso standard 9506 part(2) mms-annex-version1(3) }

   Address,
   AlarmAckRule,
   Control-State,
   DomainState,
   EC-State,
   EC-Class,
   EE-Duration,
   EE-Class,
   EventTime,
   Journal-Variable,
   LogicalStatus,
   Modifier,
   normalPriority,
   normalSeverity,
   ParameterSupportOptions,
   PhysicalStatus,
   Priority,
   ProgramInvocationState,
   Running-Mode,
   ServiceSupportOptions,
   Severity,
   Transitions,
   TypeDescription,
   ULState,
   VMDState
FROM MMS-Object-Module-1 { iso standard 9506 part(1) mms-object-model-version1(2) }
;

-- Productions

Integer8 ::= INTEGER (-128..127)

Integer16 ::= INTEGER (-32768..32767)

Integer32 ::= INTEGER (-2147483648..2147483647)

Unsigned8 ::= INTEGER (0..127)

Unsigned16 ::= INTEGER (0..32767)

Unsigned32 ::= INTEGER (0..2147483647)

FloatingPoint ::= OCTET STRING

MMSString ::= VisibleString

MMS255String ::= VisibleString (SIZE (1..255))

TimeOfDay ::= OCTET STRING (SIZE (4 | 6))

UtcTime ::= OCTET STRING (SIZE (8))

Identifier ::= VisibleString (SIZE (1..maxIdentifier))

ObjectName ::= CHOICE {
   vmd-specific [0] IMPLICIT Identifier,
   domain-specific [1] IMPLICIT SEQUENCE {
      domainID Identifier,
      itemID Identifier
   },
   aa-specific [2] IMPLICIT Identifier
}

AttachToEventCondition ::= SEQUENCE {
   eventEnrollmentName [0] ObjectName,
   eventConditionName [1] ObjectName,
   causingTransitions [2] IMPLICIT Transitions,
   acceptableDelay [3] IMPLICIT Unsigned32 OPTIONAL
}

AttachToSemaphore ::= SEQUENCE {
   semaphoreName [0] ObjectName,
   namedToken [1] IMPLICIT Identifier OPTIONAL,
   priority [2] IMPLICIT Priority DEFAULT normalPriority,
   acceptableDelay [3] IMPLICIT Unsigned32 OPTIONAL,
   controlTimeOut [4] IMPLICIT Unsigned32 OPTIONAL,
   abortOnTimeOut [5] IMPLICIT BOOLEAN OPTIONAL,
   relinquishIfConnectionLost [6] IMPLICIT BOOLEAN DEFAULT TRUE
}

TypeSpecification ::= CHOICE {
   typeName [0] ObjectName,
   typeDescription TypeDescription
}

Data ::= CHOICE {
   array [1] IMPLICIT SEQUENCE OF Data,
   structure [2] IMPLICIT SEQUENCE OF Data,
   boolean [3] IMPLICIT BOOLEAN,
   bit-string [4] IMPLICIT BIT STRING ,
   integer [5] IMPLICIT INTEGER,
   unsigned [6] IMPLICIT INTEGER,
   floating-point [7] IMPLICIT FloatingPoint,
   octet-string [9] IMPLICIT OCTET STRING,
   visible-string [10] IMPLICIT VisibleString,
   generalized-time [11] IMPLICIT GeneralizedTime,
   binary-time [12] IMPLICIT TimeOfDay,
   bcd [13] IMPLICIT INTEGER,
   booleanArray [14] IMPLICIT BIT STRING ,
   objId [15] IMPLICIT OBJECT IDENTIFIER,
   ...,
   mMSString [16] IMPLICIT MMSString
   utc-time [17] IMPLICIT UtcTime --UTC Time for mapping to IEC 61850 Timestamp
}

Start-Error ::= ProgramInvocationState

Stop-Error ::= ProgramInvocationState

Resume-Error ::= ProgramInvocationState

Reset-Error ::= ProgramInvocationState

DeleteVariableAccess-Error ::= Unsigned32

DeleteNamedVariableList-Error ::= Unsigned32

DeleteNamedType-Error ::= Unsigned32

DefineEventEnrollment-Error ::= ObjectName

DefineEventConditionList-Error ::= ObjectName

AddEventConditionListReference-Error ::= ObjectName

RemoveEventConditionListReference-Error ::= CHOICE {
   eventCondition [0] ObjectName,
   eventConditionList [1] ObjectName
}

InitiateUnitControl-Error ::= CHOICE {
   domain [0] IMPLICIT Identifier,
   programInvocation [1] IMPLICIT Identifier
}

StartUnitControl-Error ::= SEQUENCE {
   programInvocationName [0] IMPLICIT Identifier,
   programInvocationState [1] IMPLICIT ProgramInvocationState
}

StopUnitControl-Error ::= SEQUENCE {
   programInvocationName [0] IMPLICIT Identifier,
   programInvocationState [1] IMPLICIT ProgramInvocationState
}

DeleteUnitControl-Error ::= CHOICE {
   domain [0] IMPLICIT Identifier,
   programInvocation [1] IMPLICIT Identifier
}

LoadUnitControlFromFile-Error ::= CHOICE {
   none [0] IMPLICIT NULL,
   domain [1] IMPLICIT Identifier,
   programInvocation [2] IMPLICIT Identifier
}

ChangeAccessControl-Error ::= Unsigned32

ServiceError ::= SEQUENCE {
   errorClass [0] CHOICE {
      vmd-state [0] IMPLICIT INTEGER {
         other(0),
         vmd-state-conflict(1),
                  vmd-operational-problem(2),
         domain-transfer-problem(3),
         state-machine-id-invalid(4)
      } (0..4),
      application-reference [1] IMPLICIT INTEGER {
         other(0),
         application-unreachable(1),
         connection-lost(2),
         application-reference-invalid(3),
         context-unsupported(4)
      } (0..4),
      definition [2] IMPLICIT INTEGER {
         other(0),
         object-undefined(1),
         invalid-address(2),
         type-unsupported(3),
         type-inconsistent(4),
         object-exists(5),
         object-attribute-inconsistent(6)
      } (0..6),
      resource [3] IMPLICIT INTEGER {
         other(0),
         memory-unavailable(1),
         processor-resource-unavailable(2),
         mass-storage-unavailable(3),
         capability-unavailable(4),
         capability-unknown(5)
      } (0..5),
      service [4] IMPLICIT INTEGER {
         other(0),
         primitives-out-of-sequence(1),
         object-state-conflict(2),
         continuation-invalid(4),
         object-constraint-conflict(5)
      } (0..5),
      service-preempt [5] IMPLICIT INTEGER {
         other(0),
         timeout(1),
         deadlock(2),
         cancel(3)
      } (0..3),
      time-resolution [6] IMPLICIT INTEGER {
         other(0),
         unsupportable-time-resolution(1)
      } (0..1),
      access [7] IMPLICIT INTEGER {
         other(0),
         object-access-unsupported(1),
         object-non-existent(2),
         object-access-denied(3),
         object-invalidated(4)
      } (0..4),
      initiate [8] IMPLICIT INTEGER {
         other(0),
         max-services-outstanding-calling-insufficient(3),
         max-services-outstanding-called-insufficient(4),
         service-CBB-insufficient(5),
         parameter-CBB-insufficient(6),
         nesting-level-insufficient(7)
      } (0..7),
      conclude [9] IMPLICIT INTEGER {
         other(0),
         further-communication-required(1)
      } (0..1),
      cancel [10] IMPLICIT INTEGER {
         other(0),
         invoke-id-unknown(1),
         cancel-not-possible(2)
      } (0..2),
      file [11] IMPLICIT INTEGER {
         other(0),
         filename-ambiguous(1),
         file-busy(2),
         filename-syntax-error(3),
         content-type-invalid(4),
         position-invalid(5),
         file-access-denied(6),
         file-non-existent(7),
         duplicate-filename(8),
         insufficient-space-in-filestore(9)
      } (0..9),
      others [12] IMPLICIT INTEGER
   },
   additionalCode [1] IMPLICIT INTEGER OPTIONAL,
   additionalDescription [2] IMPLICIT VisibleString OPTIONAL,
   serviceSpecificInfo [3] CHOICE {
      obtainFile [0] IMPLICIT ObtainFile-Error,
      start [1] IMPLICIT Start-Error,
      stop [2] IMPLICIT Stop-Error,
      resume [3] IMPLICIT Resume-Error,
      reset [4] IMPLICIT Reset-Error,
      deleteVariableAccess [5] IMPLICIT DeleteVariableAccess-Error,
      deleteNamedVariableList [6] IMPLICIT DeleteNamedVariableList-Error,
      deleteNamedType [7] IMPLICIT DeleteNamedType-Error,
      defineEventEnrollment-Error [8] DefineEventEnrollment-Error,
      fileRename [9] IMPLICIT FileRename-Error,
      additionalService [10] IMPLICIT NULL,
      changeAccessControl [11] IMPLICIT ChangeAccessControl-Error
   } OPTIONAL
}

Initiate-ErrorPDU ::= ServiceError

Conclude-RequestPDU ::= NULL

Conclude-ResponsePDU ::= NULL

Conclude-ErrorPDU ::= ServiceError

Cancel-RequestPDU ::= Unsigned32

Cancel-ResponsePDU ::= Unsigned32

OperationState ::= INTEGER {
   idle(0),
   loaded(1),
   ready(2),
   executing(3),
   motion-paused(4),
   manualInterventionRequired(5)
} (0..5)

ExtendedStatus ::= BIT STRING {
   safetyInterlocksViolated(0),
   anyPhysicalResourcePowerOn(1),
   allPhysicalResourcesCalibrated(2),
   localControl(3)
} (SIZE (4))

Status-Request ::= BOOLEAN

Status ::= SEQUENCE {
   vmdLogicalStatus [0] IMPLICIT INTEGER {
      state-changes-allowed(0),
      no-state-changes-allowed(1),
      limited-services-permitted(2),
      support-services-allowed(3)
   } (0..3),
   vmdPhysicalStatus [1] IMPLICIT INTEGER {
      operational(0),
      partially-operational(1),
      inoperable(2),
      needs-commissioning(3)
   } (0..3),
   localDetail [2] IMPLICIT BIT STRING  (SIZE (0..128)) OPTIONAL
}

Status-Response ::= Status

UnsolicitedStatus ::= Status

Identify-Request ::= NULL

Rename-Response ::= NULL

VMDStop-Request ::= NULL

VMDStop-Response ::= NULL

VMDReset-Request ::= BOOLEAN

VMDReset-Response ::= Status

InitiateDownloadSequence-Response ::= NULL

DownloadSegment-Request ::= Identifier

TerminateDownloadSequence-Response ::= NULL

InitiateUploadSequence-Request ::= Identifier

UploadSegment-Request ::= Integer32

TerminateUploadSequence-Request ::= Integer32

TerminateUploadSequence-Response ::= NULL

RequestDomainDownload-Response ::= NULL

RequestDomainUpload-Response ::= NULL

LoadDomainContent-Response ::= NULL

StoreDomainContent-Response ::= NULL

DeleteDomain-Request ::= Identifier

DeleteDomain-Response ::= NULL

GetDomainAttributes-Request ::= Identifier

CreateProgramInvocation-Response ::= NULL

DeleteProgramInvocation-Request ::= Identifier

DeleteProgramInvocation-Response ::= NULL

Start-Response ::= NULL

Stop-Response ::= NULL

Resume-Response ::= NULL

Reset-Response ::= NULL

Kill-Response ::= NULL

GetProgramInvocationAttributes-Request ::= Identifier

Select-Response ::= NULL

AlterProgramInvocationAttributes-Response ::= NULL

ReconfigureProgramInvocation-Response ::= NULL

InitiateUnitControlLoad-Request ::= Identifier

InitiateUnitControlLoad-Response ::= NULL

UnitControlLoadSegment-Request ::= Identifier

StartUnitControl-Response ::= NULL

StopUnitControl-Request ::= Identifier

StopUnitControl-Response ::= NULL

CreateUnitControl-Response ::= NULL

AddToUnitControl-Response ::= NULL

RemoveFromUnitControl-Response ::= NULL

GetUnitControlAttributes-Request ::= Identifier

LoadUnitControlFromFile-Response ::= NULL

StoreUnitControlToFile-Response ::= NULL

DeleteUnitControl-Request ::= Identifier

DeleteUnitControl-Response ::= NULL

DataAccessError ::= INTEGER {
   object-invalidated(0),
   hardware-fault(1),
   temporarily-unavailable(2),
   object-access-denied(3),
   object-undefined(4),
   invalid-address(5),
   type-unsupported(6),
   type-inconsistent(7),
   object-attribute-inconsistent(8),
   object-access-unsupported(9),
   object-non-existent(10),
   object-value-invalid(11)
} (0..11)

DefineNamedVariable-Response ::= NULL

DefineNamedVariableList-Response ::= NULL

GetNamedVariableListAttributes-Request ::= ObjectName

DefineNamedType-Response ::= NULL

GetNamedTypeAttributes-Request ::= ObjectName

GetDataExchangeAttributes-Request ::= ObjectName

RelinquishControl-Response ::= NULL

DefineSemaphore-Response ::= NULL

DeleteSemaphore-Request ::= ObjectName

DeleteSemaphore-Response ::= NULL

ReportSemaphoreStatus-Request ::= ObjectName

Input-Response ::= MMSString

Output-Response ::= NULL

TriggerEvent-Response ::= NULL

AcknowledgeEventNotification-Response ::= NULL

DefineEventCondition-Response ::= NULL

DeleteEventCondition-Response ::= Unsigned32

GetEventConditionAttributes-Request ::= ObjectName

ReportEventConditionStatus-Request ::= ObjectName

AlterEventConditionMonitoring-Response ::= NULL

DefineEventAction-Response ::= NULL

DeleteEventAction-Response ::= Unsigned32

GetEventActionAttributes-Request ::= ObjectName

ReportEventActionStatus-Request ::= ObjectName

ReportEventActionStatus-Response ::= Unsigned32

DefineEventEnrollment-Response ::= NULL

DeleteEventEnrollment-Response ::= Unsigned32

ReportEventEnrollmentStatus-Request ::= ObjectName

EE-State ::= INTEGER {
   disabled(0),
   idle(1),
   active(2),
   activeNoAckA(3),
   idleNoAckI(4),
   idleNoAckA(5),
   idleAcked(6),
   activeAcked(7),
   undefined(8)
}

DefineEventConditionList-Response ::= NULL

DeleteEventConditionList-Request ::= ObjectName

DeleteEventConditionList-Response ::= NULL

AddEventConditionListReference-Response ::= NULL

RemoveEventConditionListReference-Response ::= NULL

GetEventConditionListAttributes-Request ::= ObjectName

AlterEventConditionListMonitoring-Response ::= NULL

WriteJournal-Response ::= NULL

InitializeJournal-Response ::= Unsigned32

ReportJournalStatus-Request ::= ObjectName

CreateJournal-Response ::= NULL

DeleteJournal-Response ::= NULL

ObjectClass ::= CHOICE {
   basicObjectClass [0] IMPLICIT INTEGER {
      namedVariable(0),
      scatteredAccess(1),
      namedVariableList(2),
      namedType(3),
      semaphore(4),
      eventCondition(5),
      eventAction(6),
      eventEnrollment(7),
      journal(8),
      domain(9),
      programInvocation(10),
      operatorStation(11)
   } (0..11)
}

GetNameList-Request ::= SEQUENCE {
   objectClass [0] ObjectClass,
   objectScope [1] CHOICE {
      vmdSpecific [0] IMPLICIT NULL,
      domainSpecific [1] IMPLICIT Identifier,
      aaSpecific [2] IMPLICIT NULL
   },
   continueAfter [2] IMPLICIT Identifier OPTIONAL
}

Rename-Request ::= SEQUENCE {
   objectClass [0] ObjectClass,
   currentName [1] ObjectName,
   newIdentifier [2] IMPLICIT Identifier
}

AlternateAccessSelection ::= CHOICE {
   selectAlternateAccess [0] IMPLICIT SEQUENCE {
      accessSelection CHOICE {
         component [0] IMPLICIT Identifier,
         index [1] IMPLICIT Unsigned32,
         indexRange [2] IMPLICIT SEQUENCE {
            lowIndex [0] IMPLICIT Unsigned32,
            numberOfElements [1] IMPLICIT Unsigned32
         },
         allElements [3] IMPLICIT NULL
      },
      alternateAccess AlternateAccess
   },
   selectAccess CHOICE {
      component [1] IMPLICIT Identifier,
      index [2] IMPLICIT Unsigned32,
      indexRange [3] IMPLICIT SEQUENCE {
         lowIndex [0] IMPLICIT Unsigned32,
         numberOfElements [1] IMPLICIT Unsigned32
      },
      allElements [4] IMPLICIT NULL
   }
}

AlternateAccess ::= SEQUENCE OF CHOICE {
   unnamed AlternateAccessSelection,
   named [5] IMPLICIT SEQUENCE {
      componentName [0] IMPLICIT Identifier,
      access AlternateAccessSelection
   }
}

VariableSpecification ::= CHOICE {
   name [0] ObjectName,
   address [1] Address,
   variableDescription [2] IMPLICIT SEQUENCE {
      address Address,
      typeSpecification TypeSpecification
   },
   scatteredAccessDescription [3] IMPLICIT ScatteredAccessDescription,
   invalidated [4] IMPLICIT NULL
}

VariableAccessSpecification ::= CHOICE {
   listOfVariable [0] IMPLICIT SEQUENCE OF SEQUENCE {
      variableSpecification VariableSpecification,
      alternateAccess [5] IMPLICIT AlternateAccess OPTIONAL
   },
   variableListName [1] ObjectName
}

Read-Request ::= SEQUENCE {
   specificationWithResult [0] IMPLICIT BOOLEAN DEFAULT FALSE,
   variableAccessSpecification [1] VariableAccessSpecification
}

Write-Request ::= SEQUENCE {
   variableAccessSpecification VariableAccessSpecification,
   listOfData [0] IMPLICIT SEQUENCE OF Data
}

GetVariableAccessAttributes-Request ::= CHOICE {
   name [0] ObjectName,
   address [1] Address
}

DefineNamedVariable-Request ::= SEQUENCE {
   variableName [0] ObjectName,
   address [1] Address,
   typeSpecification [2] TypeSpecification OPTIONAL
}

DeleteVariableAccess-Request ::= SEQUENCE {
   scopeOfDelete [0] IMPLICIT INTEGER {
      specific(0),
      aa-specific(1),
      domain(2),
      vmd(3)
   } (0..3) DEFAULT specific,
   listOfName [1] IMPLICIT SEQUENCE OF ObjectName OPTIONAL,
   domainName [2] IMPLICIT Identifier OPTIONAL
}

DefineNamedVariableList-Request ::= SEQUENCE {
   variableListName ObjectName,
   listOfVariable [0] IMPLICIT SEQUENCE OF SEQUENCE {
      variableSpecification VariableSpecification,
      alternateAccess [5] IMPLICIT AlternateAccess OPTIONAL
   }
}

DeleteNamedVariableList-Request ::= SEQUENCE {
   scopeOfDelete [0] IMPLICIT INTEGER {
      specific(0),
      aa-specific(1),
      domain(2),
      vmd(3)
   } (0..3) DEFAULT specific,
   listOfVariableListName [1] IMPLICIT SEQUENCE OF ObjectName OPTIONAL,
   domainName [2] IMPLICIT Identifier OPTIONAL
}

DefineNamedType-Request ::= SEQUENCE {
   typeName ObjectName,
   typeSpecification TypeSpecification
}

DeleteNamedType-Request ::= SEQUENCE {
   scopeOfDelete [0] IMPLICIT INTEGER {
      specific(0),
      aa-specific(1),
      domain(2),
      vmd(3)
   } (0..3) DEFAULT specific,
   listOfTypeName [1] IMPLICIT SEQUENCE OF ObjectName OPTIONAL,
   domainName [2] IMPLICIT Identifier OPTIONAL
}

Input-Request ::= SEQUENCE {
   operatorStationName [0] IMPLICIT Identifier,
   echo [1] IMPLICIT BOOLEAN DEFAULT TRUE,
   listOfPromptData [2] IMPLICIT SEQUENCE OF MMSString OPTIONAL,
   inputTimeOut [3] IMPLICIT Unsigned32 OPTIONAL
}

Output-Request ::= SEQUENCE {
   operatorStationName [0] IMPLICIT Identifier,
   listOfOutputData [1] IMPLICIT SEQUENCE OF MMSString
}

TakeControl-Request ::= SEQUENCE {
   semaphoreName [0] ObjectName,
   namedToken [1] IMPLICIT Identifier OPTIONAL,
   priority [2] IMPLICIT Priority DEFAULT normalPriority,
   acceptableDelay [3] IMPLICIT Unsigned32 OPTIONAL,
   controlTimeOut [4] IMPLICIT Unsigned32 OPTIONAL,
   abortOnTimeOut [5] IMPLICIT BOOLEAN OPTIONAL,
   relinquishIfConnectionLost [6] IMPLICIT BOOLEAN DEFAULT TRUE,
   applicationToPreempt [7] IMPLICIT ApplicationReference OPTIONAL
}

RelinquishControl-Request ::= SEQUENCE {
   semaphoreName [0] ObjectName,
   namedToken [1] IMPLICIT Identifier OPTIONAL
}

DefineSemaphore-Request ::= SEQUENCE {
   semaphoreName [0] ObjectName,
   numberOfTokens [1] IMPLICIT Unsigned16
}

ReportPoolSemaphoreStatus-Request ::= SEQUENCE {
   semaphoreName [0] ObjectName,
   nameToStartAfter [1] IMPLICIT Identifier OPTIONAL
}

ReportSemaphoreEntryStatus-Request ::= SEQUENCE {
   semaphoreName [0] ObjectName,
   state [1] IMPLICIT INTEGER {
      queued(0),
      owner(1),
      hung(2)
   } (0..2),
   entryIDToStartAfter [2] IMPLICIT OCTET STRING OPTIONAL
}

InitiateDownloadSequence-Request ::= SEQUENCE {
   domainName [0] IMPLICIT Identifier,
   listOfCapabilities [1] IMPLICIT SEQUENCE OF MMSString,
   sharable [2] IMPLICIT BOOLEAN
}

TerminateDownloadSequence-Request ::= SEQUENCE {
   domainName [0] IMPLICIT Identifier,
   discard [1] IMPLICIT ServiceError OPTIONAL
}

FileName ::= SEQUENCE OF GraphicString

RequestDomainDownload-Request ::= SEQUENCE {
   domainName [0] IMPLICIT Identifier,
   listOfCapabilities [1] IMPLICIT SEQUENCE OF MMSString OPTIONAL,
   sharable [2] IMPLICIT BOOLEAN,
   fileName [4] IMPLICIT FileName
}

RequestDomainUpload-Request ::= SEQUENCE {
   domainName [0] IMPLICIT Identifier,
   fileName [1] IMPLICIT FileName
}

LoadDomainContent-Request ::= SEQUENCE {
   domainName [0] IMPLICIT Identifier,
   listOfCapabilities [1] IMPLICIT SEQUENCE OF MMSString OPTIONAL,
   sharable [2] IMPLICIT BOOLEAN,
   fileName [4] IMPLICIT FileName,
   thirdParty [5] IMPLICIT ApplicationReference OPTIONAL
}

StoreDomainContent-Request ::= SEQUENCE {
   domainName [0] IMPLICIT Identifier,
   fileName [1] IMPLICIT FileName,
   thirdParty [2] IMPLICIT ApplicationReference OPTIONAL
}

CreateProgramInvocation-Request ::= SEQUENCE {
   programInvocationName [0] IMPLICIT Identifier,
   listOfDomainNames [1] IMPLICIT SEQUENCE OF Identifier,
   reusable [2] IMPLICIT BOOLEAN DEFAULT TRUE,
   monitorType [3] IMPLICIT BOOLEAN OPTIONAL
}

Start-Request ::= SEQUENCE {
   programInvocationName [0] IMPLICIT Identifier,
   executionArgument CHOICE {
      simpleString [1] IMPLICIT MMSString,
      encodedString EXTERNAL,
      embeddedString EMBEDDED PDV
   } OPTIONAL
}

Stop-Request ::= SEQUENCE {
   programInvocationName [0] IMPLICIT Identifier
}

Resume-Request ::= SEQUENCE {
   programInvocationName [0] IMPLICIT Identifier,
   executionArgument CHOICE {
      simpleString [1] IMPLICIT MMSString,
      encodedString EXTERNAL,
      enmbeddedString EMBEDDED PDV
   } OPTIONAL
}

Reset-Request ::= SEQUENCE {
   programInvocationName [0] IMPLICIT Identifier
}

Kill-Request ::= SEQUENCE {
   programInvocationName [0] IMPLICIT Identifier
}

DefineEventCondition-Request ::= SEQUENCE {
   eventConditionName [0] ObjectName,
   class [1] IMPLICIT EC-Class,
   priority [2] IMPLICIT Priority DEFAULT normalPriority,
   severity [3] IMPLICIT Unsigned8 DEFAULT normalSeverity,
   alarmSummaryReports [4] IMPLICIT BOOLEAN OPTIONAL,
   monitoredVariable [6] VariableSpecification OPTIONAL,
   evaluationInterval [7] IMPLICIT Unsigned32 OPTIONAL
}

DeleteEventCondition-Request ::= CHOICE {
   specific [0] IMPLICIT SEQUENCE OF ObjectName,
   aa-specific [1] IMPLICIT NULL,
   domain [2] IMPLICIT Identifier,
   vmd [3] IMPLICIT NULL
}

AlterEventConditionMonitoring-Request ::= SEQUENCE {
   eventConditionName [0] ObjectName,
   enabled [1] IMPLICIT BOOLEAN OPTIONAL,
   priority [2] IMPLICIT Priority OPTIONAL,
   alarmSummaryReports [3] IMPLICIT BOOLEAN OPTIONAL,
   evaluationInterval [4] IMPLICIT Unsigned32 OPTIONAL
}

TriggerEvent-Request ::= SEQUENCE {
   eventConditionName [0] ObjectName,
   priority [1] IMPLICIT Priority OPTIONAL
}

StartCount ::= CHOICE {
   noLimit [0] IMPLICIT NULL,
   cycleCount [1] IMPLICIT INTEGER,
   stepCount [2] IMPLICIT INTEGER
}

DefineEventAction-Request ::= SEQUENCE {
   eventActionName [0] ObjectName,
   listOfModifier [1] IMPLICIT SEQUENCE OF Modifier OPTIONAL,
   confirmedServiceRequest [2] ConfirmedServiceRequest
}

DeleteEventAction-Request ::= CHOICE {
   specific [0] IMPLICIT SEQUENCE OF ObjectName,
   aa-specific [1] IMPLICIT NULL,
   domain [3] IMPLICIT Identifier,
   vmd [4] IMPLICIT NULL
}

DefineEventEnrollment-Request ::= SEQUENCE {
   eventEnrollmentName [0] ObjectName,
   eventConditionName [1] ObjectName,
   eventConditionTransitions [2] IMPLICIT Transitions,
   alarmAcknowledgmentRule [3] IMPLICIT AlarmAckRule,
   eventActionName [4] ObjectName OPTIONAL,
   clientApplication [5] ApplicationReference OPTIONAL
}

DeleteEventEnrollment-Request ::= CHOICE {
   specific [0] IMPLICIT SEQUENCE OF ObjectName,
   ec [1] ObjectName,
   ea [2] ObjectName
}

AlterEventEnrollment-Request ::= SEQUENCE {
   eventEnrollmentName [0] ObjectName,
   eventConditionTransitions [1] IMPLICIT Transitions OPTIONAL,
   alarmAcknowledgmentRule [2] IMPLICIT AlarmAckRule OPTIONAL
}

GetEventEnrollmentAttributes-Request ::= SEQUENCE {
   scopeOfRequest [0] IMPLICIT INTEGER {
      specific(0),
      client(1),
      ec(2),
      ea(3)
   } (0..3) DEFAULT client,
   eventEnrollmentNames [1] IMPLICIT SEQUENCE OF ObjectName OPTIONAL,
   clientApplication [2] ApplicationReference OPTIONAL,
   eventConditionName [3] ObjectName OPTIONAL,
   eventActionName [4] ObjectName OPTIONAL,
   continueAfter [5] ObjectName OPTIONAL
}

AcknowledgeEventNotification-Request ::= SEQUENCE {
   eventEnrollmentName [0] ObjectName,
   acknowledgedState [2] IMPLICIT EC-State,
   timeOfAcknowledgedTransition [3] EventTime
}

GetAlarmSummary-Request ::= SEQUENCE {
   enrollmentsOnly [0] IMPLICIT BOOLEAN DEFAULT TRUE,
   activeAlarmsOnly [1] IMPLICIT BOOLEAN DEFAULT TRUE,
   acknowledgementFilter [2] IMPLICIT INTEGER {
      not-acked(0),
      acked(1),
      all(2)
   } (0..2) DEFAULT not-acked,
   severityFilter [3] IMPLICIT SEQUENCE {
      mostSevere [0] IMPLICIT Unsigned8,
      leastSevere [1] IMPLICIT Unsigned8
   } OPTIONAL, -- DEFAULT { mostSevere 0, leastSevere 127 }
   continueAfter [5] ObjectName OPTIONAL
}

GetAlarmEnrollmentSummary-Request ::= SEQUENCE {
   enrollmentsOnly [0] IMPLICIT BOOLEAN DEFAULT TRUE,
   activeAlarmsOnly [1] IMPLICIT BOOLEAN DEFAULT TRUE,
   acknowledgementFilter [2] IMPLICIT INTEGER {
      not-acked(0),
      acked(1),
      all(2)
   } (0..2) DEFAULT not-acked,
   severityFilter [3] IMPLICIT SEQUENCE {
      mostSevere [0] IMPLICIT Unsigned8,
      leastSevere [1] IMPLICIT Unsigned8
   } OPTIONAL, -- DEFAULT { mostSevere 0, leastSevere 127 }
   continueAfter [5] ObjectName OPTIONAL
}

ReadJournal-Request ::= SEQUENCE {
   journalName [0] ObjectName,
   rangeStartSpecification [1] CHOICE {
      startingTime [0] IMPLICIT TimeOfDay,
      startingEntry [1] IMPLICIT OCTET STRING
   } OPTIONAL,
   rangeStopSpecification [2] CHOICE {
      endingTime [0] IMPLICIT TimeOfDay,
      numberOfEntries [1] IMPLICIT Integer32
   } OPTIONAL,
   listOfVariables [4] IMPLICIT SEQUENCE OF VisibleString OPTIONAL,
   entryToStartAfter [5] IMPLICIT SEQUENCE {
      timeSpecification [0] IMPLICIT TimeOfDay,
      entrySpecification [1] IMPLICIT OCTET STRING
   } OPTIONAL
}

EntryContent ::= SEQUENCE {
   occurrenceTime [0] IMPLICIT TimeOfDay,
   entryForm CHOICE {
      data [2] IMPLICIT SEQUENCE {
         event [0] IMPLICIT SEQUENCE {
            eventConditionName [0] ObjectName,
            currentState [1] IMPLICIT EC-State
         } OPTIONAL,
         listOfVariables [1] IMPLICIT SEQUENCE OF Journal-Variable OPTIONAL
      },
      annotation [3] MMSString
   }
}

WriteJournal-Request ::= SEQUENCE {
   journalName [0] ObjectName,
   listOfJournalEntry [1] IMPLICIT SEQUENCE OF EntryContent
}

InitializeJournal-Request ::= SEQUENCE {
   journalName [0] ObjectName,
   limitSpecification [1] IMPLICIT SEQUENCE {
      limitingTime [0] IMPLICIT TimeOfDay,
      limitingEntry [1] IMPLICIT OCTET STRING OPTIONAL
   } OPTIONAL
}

CreateJournal-Request ::= SEQUENCE {
   journalName [0] ObjectName
}

DeleteJournal-Request ::= SEQUENCE {
   journalName [0] ObjectName
}

GetCapabilityList-Request ::= SEQUENCE {
   continueAfter MMSString OPTIONAL
}

Select-Request ::= SEQUENCE {
   controlling [0] IMPLICIT Identifier OPTIONAL,
   controlled [1] IMPLICIT SEQUENCE OF Identifier OPTIONAL
}

AlterProgramInvocationAttributes-Request ::= SEQUENCE {
   programInvocation [0] IMPLICIT Identifier,
   startCount [1] StartCount OPTIONAL -- DEFAULT cycleCount: 1
}

UnitControlUpload-Request ::= SEQUENCE {
   unitControlName [0] IMPLICIT Identifier,
   continueAfter CHOICE {
      domain [1] IMPLICIT Identifier,
      ulsmID [2] IMPLICIT INTEGER,
      programInvocation [3] IMPLICIT Identifier
   } OPTIONAL
}

StartUnitControl-Request ::= SEQUENCE {
   unitControlName [0] IMPLICIT Identifier,
   executionArgument CHOICE {
      simpleString [1] IMPLICIT MMSString,
      encodedString EXTERNAL,
      enmbeddedString EMBEDDED PDV
   } OPTIONAL
}

CreateUnitControl-Request ::= SEQUENCE {
   unitControl [0] IMPLICIT Identifier,
   domains [1] IMPLICIT SEQUENCE OF Identifier,
   programInvocations [2] IMPLICIT SEQUENCE OF Identifier
}

AddToUnitControl-Request ::= SEQUENCE {
   unitControl [0] IMPLICIT Identifier,
   domains [1] IMPLICIT SEQUENCE OF Identifier,
   programInvocations [2] IMPLICIT SEQUENCE OF Identifier
}

RemoveFromUnitControl-Request ::= SEQUENCE {
   unitControl [0] IMPLICIT Identifier,
   domains [1] IMPLICIT SEQUENCE OF Identifier,
   programInvocations [2] IMPLICIT SEQUENCE OF Identifier
}

LoadUnitControlFromFile-Request ::= SEQUENCE {
   unitControlName [0] IMPLICIT Identifier,
   fileName [1] IMPLICIT FileName,
   thirdParty [2] IMPLICIT ApplicationReference OPTIONAL
}

StoreUnitControlToFile-Request ::= SEQUENCE {
   unitControlName [0] IMPLICIT Identifier,
   fileName [1] IMPLICIT FileName,
   thirdParty [2] IMPLICIT ApplicationReference OPTIONAL
}

DefineEventConditionList-Request ::= SEQUENCE {
   eventConditionListName [0] ObjectName,
   listOfEventConditionName [1] IMPLICIT SEQUENCE OF ObjectName,
   listOfEventConditionListName [2] IMPLICIT SEQUENCE OF ObjectName OPTIONAL
}

AddEventConditionListReference-Request ::= SEQUENCE {
   eventConditionListName [0] ObjectName,
   listOfEventConditionName [1] IMPLICIT SEQUENCE OF ObjectName,
   listOfEventConditionListName [2] IMPLICIT SEQUENCE OF ObjectName OPTIONAL
}

RemoveEventConditionListReference-Request ::= SEQUENCE {
   eventConditionListName [0] ObjectName,
   listOfEventConditionName [1] IMPLICIT SEQUENCE OF ObjectName,
   listOfEventConditionListName [2] IMPLICIT SEQUENCE OF ObjectName
}

ReportEventConditionListStatus-Request ::= SEQUENCE {
   eventConditionListName [0] ObjectName,
   continueAfter [1] IMPLICIT Identifier OPTIONAL
}

AlterEventConditionListMonitoring-Request ::= SEQUENCE {
   eventConditionListName [0] ObjectName,
   enabled [1] IMPLICIT BOOLEAN,
   priorityChange [2] CHOICE {
      priorityValue [0] IMPLICIT INTEGER,
      priorityReset [1] IMPLICIT NULL
   } OPTIONAL
}

ExchangeData-Request ::= SEQUENCE {
   dataExchangeName [0] ObjectName,
   listOfRequestData [1] IMPLICIT SEQUENCE OF Data
}

ConfirmedServiceRequest ::= CHOICE {
   status [0] IMPLICIT Status-Request,
   getNameList [1] IMPLICIT GetNameList-Request,
   identify [2] IMPLICIT Identify-Request,
   rename [3] IMPLICIT Rename-Request,
   read [4] IMPLICIT Read-Request,
   write [5] IMPLICIT Write-Request,
   getVariableAccessAttributes [6] GetVariableAccessAttributes-Request,
   defineNamedVariable [7] IMPLICIT DefineNamedVariable-Request,
   defineScatteredAccess [8] IMPLICIT DefineScatteredAccess-Request,
   getScatteredAccessAttributes [9] GetScatteredAccessAttributes-Request,
   deleteVariableAccess [10] IMPLICIT DeleteVariableAccess-Request,
   defineNamedVariableList [11] IMPLICIT DefineNamedVariableList-Request,
   getNamedVariableListAttributes [12] GetNamedVariableListAttributes-Request,
   deleteNamedVariableList [13] IMPLICIT DeleteNamedVariableList-Request,
   defineNamedType [14] IMPLICIT DefineNamedType-Request,
   getNamedTypeAttributes [15] GetNamedTypeAttributes-Request,
   deleteNamedType [16] IMPLICIT DeleteNamedType-Request,
   input [17] IMPLICIT Input-Request,
   output [18] IMPLICIT Output-Request,
   takeControl [19] IMPLICIT TakeControl-Request,
   relinquishControl [20] IMPLICIT RelinquishControl-Request,
   defineSemaphore [21] IMPLICIT DefineSemaphore-Request,
   deleteSemaphore [22] DeleteSemaphore-Request,
   reportSemaphoreStatus [23] ReportSemaphoreStatus-Request,
   reportPoolSemaphoreStatus [24] IMPLICIT ReportPoolSemaphoreStatus-Request,
   reportSemaphoreEntryStatus [25] IMPLICIT ReportSemaphoreEntryStatus-Request,
   initiateDownloadSequence [26] IMPLICIT InitiateDownloadSequence-Request,
   downloadSegment [27] IMPLICIT DownloadSegment-Request,
   terminateDownloadSequence [28] IMPLICIT TerminateDownloadSequence-Request,
   initiateUploadSequence [29] IMPLICIT InitiateUploadSequence-Request,
   uploadSegment [30] IMPLICIT UploadSegment-Request,
   terminateUploadSequence [31] IMPLICIT TerminateUploadSequence-Request,
   requestDomainDownload [32] IMPLICIT RequestDomainDownload-Request,
   requestDomainUpload [33] IMPLICIT RequestDomainUpload-Request,
   loadDomainContent [34] IMPLICIT LoadDomainContent-Request,
   storeDomainContent [35] IMPLICIT StoreDomainContent-Request,
   deleteDomain [36] IMPLICIT DeleteDomain-Request,
   getDomainAttributes [37] IMPLICIT GetDomainAttributes-Request,
   createProgramInvocation [38] IMPLICIT CreateProgramInvocation-Request,
   deleteProgramInvocation [39] IMPLICIT DeleteProgramInvocation-Request,
   start [40] IMPLICIT Start-Request,
   stop [41] IMPLICIT Stop-Request,
   resume [42] IMPLICIT Resume-Request,
   reset [43] IMPLICIT Reset-Request,
   kill [44] IMPLICIT Kill-Request,
   getProgramInvocationAttributes [45] IMPLICIT GetProgramInvocationAttributes-Request,
   obtainFile [46] IMPLICIT ObtainFile-Request,
   defineEventCondition [47] IMPLICIT DefineEventCondition-Request,
   deleteEventCondition [48] DeleteEventCondition-Request,
   getEventConditionAttributes [49] GetEventConditionAttributes-Request,
   reportEventConditionStatus [50] ReportEventConditionStatus-Request,
   alterEventConditionMonitoring [51] IMPLICIT AlterEventConditionMonitoring-Request,
   triggerEvent [52] IMPLICIT TriggerEvent-Request,
   defineEventAction [53] IMPLICIT DefineEventAction-Request,
   deleteEventAction [54] DeleteEventAction-Request,
   getEventActionAttributes [55] GetEventActionAttributes-Request,
   reportEventActionStatus [56] ReportEventActionStatus-Request,
   defineEventEnrollment [57] IMPLICIT DefineEventEnrollment-Request,
   deleteEventEnrollment [58] DeleteEventEnrollment-Request,
   alterEventEnrollment [59] IMPLICIT AlterEventEnrollment-Request,
   reportEventEnrollmentStatus [60] ReportEventEnrollmentStatus-Request,
   getEventEnrollmentAttributes [61] IMPLICIT GetEventEnrollmentAttributes-Request,
   acknowledgeEventNotification [62] IMPLICIT AcknowledgeEventNotification-Request,
   getAlarmSummary [63] IMPLICIT GetAlarmSummary-Request,
   getAlarmEnrollmentSummary [64] IMPLICIT GetAlarmEnrollmentSummary-Request,
   readJournal [65] IMPLICIT ReadJournal-Request,
   writeJournal [66] IMPLICIT WriteJournal-Request,
   initializeJournal [67] IMPLICIT InitializeJournal-Request,
   reportJournalStatus [68] ReportJournalStatus-Request,
   createJournal [69] IMPLICIT CreateJournal-Request,
   deleteJournal [70] IMPLICIT DeleteJournal-Request,
   getCapabilityList [71] IMPLICIT GetCapabilityList-Request,
   fileOpen [72] IMPLICIT FileOpen-Request,
   fileRead [73] IMPLICIT FileRead-Request,
   fileClose [74] IMPLICIT FileClose-Request,
   fileRename [75] IMPLICIT FileRename-Request,
   fileDelete [76] IMPLICIT FileDelete-Request,
   fileDirectory [77] IMPLICIT FileDirectory-Request,
   getDataExchangeAttributes [80] GetDataExchangeAttributes-Request,
   exchangeData [81] IMPLICIT ExchangeData-Request
}

Confirmed-RequestPDU ::= SEQUENCE {
   invokeID Unsigned32,
   listOfModifiers SEQUENCE OF Modifier OPTIONAL,
   service ConfirmedServiceRequest
}

GetNameList-Response ::= SEQUENCE {
   listOfIdentifier [0] IMPLICIT SEQUENCE OF Identifier,
   moreFollows [1] IMPLICIT BOOLEAN DEFAULT TRUE
}

Identify-Response ::= SEQUENCE {
   vendorName [0] IMPLICIT MMSString,
   modelName [1] IMPLICIT MMSString,
   revision [2] IMPLICIT MMSString,
   listOfAbstractSyntaxes [3] IMPLICIT SEQUENCE OF OBJECT IDENTIFIER OPTIONAL
}

AccessResult ::= CHOICE {
   failure [0] IMPLICIT DataAccessError,
   success Data
}

Read-Response ::= SEQUENCE {
   variableAccessSpecification [0] VariableAccessSpecification OPTIONAL,
   listOfAccessResult [1] IMPLICIT SEQUENCE OF AccessResult
}

GetVariableAccessAttributes-Response ::= SEQUENCE {
   mmsDeletable [0] IMPLICIT BOOLEAN,
   address [1] Address OPTIONAL,
   typeDescription [2] TypeDescription
}

DeleteVariableAccess-Response ::= SEQUENCE {
   numberMatched [0] IMPLICIT Unsigned32,
   numberDeleted [1] IMPLICIT Unsigned32
}

GetNamedVariableListAttributes-Response ::= SEQUENCE {
   mmsDeletable [0] IMPLICIT BOOLEAN,
   listOfVariable [1] IMPLICIT SEQUENCE OF SEQUENCE {
      variableSpecification VariableSpecification,
      alternateAccess [5] IMPLICIT AlternateAccess OPTIONAL
   }
}

DeleteNamedVariableList-Response ::= SEQUENCE {
   numberMatched [0] IMPLICIT Unsigned32,
   numberDeleted [1] IMPLICIT Unsigned32
}

GetNamedTypeAttributes-Response ::= SEQUENCE {
   mmsDeletable [0] IMPLICIT BOOLEAN,
   typeSpecification TypeSpecification
}

DeleteNamedType-Response ::= SEQUENCE {
   numberMatched [0] IMPLICIT Unsigned32,
   numberDeleted [1] IMPLICIT Unsigned32
}

TakeControl-Response ::= CHOICE {
   noResult [0] IMPLICIT NULL,
   namedToken [1] IMPLICIT Identifier
}

ReportSemaphoreStatus-Response ::= SEQUENCE {
   mmsDeletable [0] IMPLICIT BOOLEAN,
   class [1] IMPLICIT INTEGER {
      token(0),
      pool(1)
   } (0..1),
   numberOfTokens [2] IMPLICIT Unsigned16,
   numberOfOwnedTokens [3] IMPLICIT Unsigned16,
   numberOfHungTokens [4] IMPLICIT Unsigned16
}

ReportPoolSemaphoreStatus-Response ::= SEQUENCE {
   listOfNamedTokens [0] IMPLICIT SEQUENCE OF CHOICE {
      freeNamedToken [0] IMPLICIT Identifier,
      ownedNamedToken [1] IMPLICIT Identifier,
      hungNamedToken [2] IMPLICIT Identifier
   },
   moreFollows [1] IMPLICIT BOOLEAN DEFAULT TRUE
}

SemaphoreEntry ::= SEQUENCE {
   entryID [0] IMPLICIT OCTET STRING,
   entryClass [1] IMPLICIT INTEGER {
      simple(0),
      modifier(1)
   } (0..1),
   applicationReference [2] ApplicationReference,
   namedToken [3] IMPLICIT Identifier OPTIONAL,
   priority [4] IMPLICIT Priority DEFAULT normalPriority,
   remainingTimeOut [5] IMPLICIT Unsigned32 OPTIONAL,
   abortOnTimeOut [6] IMPLICIT BOOLEAN OPTIONAL,
   relinquishIfConnectionLost [7] IMPLICIT BOOLEAN DEFAULT TRUE
}

ReportSemaphoreEntryStatus-Response ::= SEQUENCE {
   listOfSemaphoreEntry [0] IMPLICIT SEQUENCE OF SemaphoreEntry,
   moreFollows [1] IMPLICIT BOOLEAN DEFAULT TRUE
}

LoadData ::= CHOICE {
   non-coded [0] IMPLICIT OCTET STRING,
   coded EXTERNAL,
   embedded EMBEDDED PDV
}

DownloadSegment-Response ::= SEQUENCE {
   loadData LoadData,
   moreFollows [1] IMPLICIT BOOLEAN DEFAULT TRUE
}

InitiateUploadSequence-Response ::= SEQUENCE {
   ulsmID [0] IMPLICIT Integer32,
   listOfCapabilities [1] IMPLICIT SEQUENCE OF MMSString
}

UploadSegment-Response ::= SEQUENCE {
   loadData LoadData,
   moreFollows [1] IMPLICIT BOOLEAN DEFAULT TRUE
}

GetDomainAttributes-Response ::= SEQUENCE {
   listOfCapabilities [0] IMPLICIT SEQUENCE OF MMSString,
   state [1] IMPLICIT DomainState,
   mmsDeletable [2] IMPLICIT BOOLEAN,
   sharable [3] IMPLICIT BOOLEAN,
   listOfProgramInvocations [4] IMPLICIT SEQUENCE OF Identifier,
   uploadInProgress [5] IMPLICIT Integer8
}

GetProgramInvocationAttributes-Response ::= SEQUENCE {
   state [0] IMPLICIT ProgramInvocationState,
   listOfDomainNames [1] IMPLICIT SEQUENCE OF Identifier,
   mmsDeletable [2] IMPLICIT BOOLEAN,
   reusable [3] IMPLICIT BOOLEAN,
   monitor [4] IMPLICIT BOOLEAN,
   executionArgument CHOICE {
      simpleString [5] IMPLICIT MMSString,
      encodedString EXTERNAL,
      enmbeddedString EMBEDDED PDV
   }
}

GetEventConditionAttributes-Response ::= SEQUENCE {
   mmsDeletable [0] IMPLICIT BOOLEAN DEFAULT FALSE,
   class [1] IMPLICIT EC-Class,
   priority [2] IMPLICIT Priority DEFAULT normalPriority,
   severity [3] IMPLICIT Unsigned8 DEFAULT normalSeverity,
   alarmSummaryReports [4] IMPLICIT BOOLEAN DEFAULT FALSE,
   monitoredVariable [6] CHOICE {
      variableReference [0] VariableSpecification,
      undefined [1] IMPLICIT NULL
   } OPTIONAL,
   evaluationInterval [7] IMPLICIT Unsigned32 OPTIONAL
}

ReportEventConditionStatus-Response ::= SEQUENCE {
   currentState [0] IMPLICIT EC-State,
   numberOfEventEnrollments [1] IMPLICIT Unsigned32,
   enabled [2] IMPLICIT BOOLEAN OPTIONAL,
   timeOfLastTransitionToActive [3] EventTime OPTIONAL,
   timeOfLastTransitionToIdle [4] EventTime OPTIONAL
}

GetEventActionAttributes-Response ::= SEQUENCE {
   mmsDeletable [0] IMPLICIT BOOLEAN DEFAULT FALSE,
   listOfModifier [1] IMPLICIT SEQUENCE OF Modifier,
   confirmedServiceRequest [2] ConfirmedServiceRequest
}

AlterEventEnrollment-Response ::= SEQUENCE {
   currentState [0] CHOICE {
      state [0] IMPLICIT EE-State,
      undefined [1] IMPLICIT NULL
   },
   transitionTime [1] EventTime
}

ReportEventEnrollmentStatus-Response ::= SEQUENCE {
   eventConditionTransitions [0] IMPLICIT Transitions,
   notificationLost [1] IMPLICIT BOOLEAN DEFAULT FALSE,
   duration [2] IMPLICIT EE-Duration,
   alarmAcknowledgmentRule [3] IMPLICIT AlarmAckRule OPTIONAL,
   currentState [4] IMPLICIT EE-State
}

EEAttributes ::= SEQUENCE {
   eventEnrollmentName [0] ObjectName,
   eventConditionName [1] CHOICE {
      eventCondition [0] ObjectName,
      undefined [1] IMPLICIT NULL
   },
   eventActionName [2] CHOICE {
      eventAction [0] ObjectName,
      undefined [1] IMPLICIT NULL
   } OPTIONAL,
   clientApplication [3] ApplicationReference OPTIONAL,
   mmsDeletable [4] IMPLICIT BOOLEAN DEFAULT FALSE,
   enrollmentClass [5] IMPLICIT EE-Class,
   duration [6] IMPLICIT EE-Duration DEFAULT current,
   invokeID [7] IMPLICIT Unsigned32 OPTIONAL,
   remainingAcceptableDelay [8] IMPLICIT Unsigned32 OPTIONAL,
   displayEnhancement [9] CHOICE {
      string [0] IMPLICIT VisibleString,
      index [1] IMPLICIT INTEGER,
      noEnhancement NULL
   }
}

GetEventEnrollmentAttributes-Response ::= SEQUENCE {
   listOfEEAttributes [0] IMPLICIT SEQUENCE OF EEAttributes,
   moreFollows [1] IMPLICIT BOOLEAN DEFAULT FALSE
}

EN-Additional-Detail ::= [0] CHOICE {
   string [0] IMPLICIT VisibleString,
   index [1] IMPLICIT INTEGER,
   noEnhancement NULL
}

AlarmSummary ::= SEQUENCE {
   eventConditionName [0] ObjectName,
   severity [1] IMPLICIT Unsigned8,
   currentState [2] IMPLICIT EC-State,
   unacknowledgedState [3] IMPLICIT INTEGER {
      none(0),
      active(1),
      idle(2),
      both(3)
   } (0..3),
   displayEnhancement [4] EN-Additional-Detail OPTIONAL,
   timeOfLastTransitionToActive [5] EventTime OPTIONAL,
   timeOfLastTransitionToIdle [6] EventTime OPTIONAL
}

GetAlarmSummary-Response ::= SEQUENCE {
   listOfAlarmSummary [0] IMPLICIT SEQUENCE OF AlarmSummary,
   moreFollows [1] IMPLICIT BOOLEAN DEFAULT FALSE
}

AlarmEnrollmentSummary ::= SEQUENCE {
   eventEnrollmentName [0] ObjectName,
   clientApplication [2] ApplicationReference OPTIONAL,
   severity [3] IMPLICIT Unsigned8,
   currentState [4] IMPLICIT EC-State,
   displayEnhancement [5] EN-Additional-Detail OPTIONAL,
   notificationLost [6] IMPLICIT BOOLEAN DEFAULT FALSE,
   alarmAcknowledgmentRule [7] IMPLICIT AlarmAckRule,
   enrollmentState [8] IMPLICIT EE-State OPTIONAL,
   timeOfLastTransitionToActive [9] EventTime OPTIONAL,
   timeActiveAcknowledged [10] EventTime OPTIONAL,
   timeOfLastTransitionToIdle [11] EventTime OPTIONAL,
   timeIdleAcknowledged [12] EventTime OPTIONAL
}

GetAlarmEnrollmentSummary-Response ::= SEQUENCE {
   listOfAlarmEnrollmentSummary [0] IMPLICIT SEQUENCE OF AlarmEnrollmentSummary,
   moreFollows [1] IMPLICIT BOOLEAN DEFAULT FALSE
}

JournalEntry ::= SEQUENCE {
   entryIdentifier [0] IMPLICIT OCTET STRING,
   originatingApplication [1] ApplicationReference,
   entryContent [2] IMPLICIT EntryContent
}

ReadJournal-Response ::= SEQUENCE {
   listOfJournalEntry [0] IMPLICIT SEQUENCE OF JournalEntry,
   moreFollows [1] IMPLICIT BOOLEAN DEFAULT FALSE
}

ReportJournalStatus-Response ::= SEQUENCE {
   currentEntries [0] IMPLICIT Unsigned32,
   mmsDeletable [1] IMPLICIT BOOLEAN
}

GetCapabilityList-Response ::= SEQUENCE {
   listOfCapabilities [0] IMPLICIT SEQUENCE OF MMSString,
   moreFollows [1] IMPLICIT BOOLEAN DEFAULT TRUE
}

ControlElement ::= CHOICE {
   beginDomainDef [0] SEQUENCE {
      domainName [1] IMPLICIT Identifier,
      capabilities [2] IMPLICIT SEQUENCE OF MMSString,
      sharable [3] IMPLICIT BOOLEAN,
      loadData [4] LoadData OPTIONAL
   },
   continueDomainDef [1] SEQUENCE {
      domainName [1] IMPLICIT Identifier,
      loadData [3] LoadData
   },
   endDomainDef [2] IMPLICIT Identifier,
   piDefinition [3] IMPLICIT SEQUENCE {
      piName [0] IMPLICIT Identifier,
      listOfDomains [1] IMPLICIT SEQUENCE OF Identifier,
      reusable [2] IMPLICIT BOOLEAN DEFAULT TRUE,
      monitorType [3] IMPLICIT BOOLEAN OPTIONAL,
      pIState [4] IMPLICIT ProgramInvocationState OPTIONAL
   }
}

UnitControlLoadSegment-Response ::= SEQUENCE {
   controlElements [0] IMPLICIT SEQUENCE OF ControlElement,
   moreFollows [1] IMPLICIT BOOLEAN DEFAULT TRUE
}

UnitControlUpload-Response ::= SEQUENCE {
   controlElements [0] IMPLICIT SEQUENCE OF ControlElement,
   nextElement CHOICE {
      domain [1] IMPLICIT Identifier,
      ulsmID [2] IMPLICIT INTEGER,
      programInvocation [3] IMPLICIT Identifier
   } OPTIONAL
}

GetUnitControlAttributes-Response ::= SEQUENCE {
   domains [0] IMPLICIT SEQUENCE OF Identifier,
   programInvocations [1] IMPLICIT SEQUENCE OF Identifier
}

GetEventConditionListAttributes-Response ::= SEQUENCE {
   listOfEventConditionName [1] IMPLICIT SEQUENCE OF ObjectName,
   listOfEventConditionListName [2] IMPLICIT SEQUENCE OF ObjectName OPTIONAL
}

EventConditionStatus ::= SEQUENCE {
   eventConditionName [0] ObjectName,
   currentState [1] IMPLICIT EC-State,
   numberOfEventEnrollments [2] IMPLICIT Unsigned32,
   enabled [3] IMPLICIT BOOLEAN OPTIONAL,
   timeOfLastTransitionToActive [4] EventTime OPTIONAL,
   timeOfLastTransitionToIdle [5] EventTime OPTIONAL
}

ReportEventConditionListStatus-Response ::= SEQUENCE {
   listOfEventConditionStatus [1] IMPLICIT SEQUENCE OF EventConditionStatus,
   moreFollows [2] IMPLICIT BOOLEAN DEFAULT TRUE
}

GetDataExchangeAttributes-Response ::= SEQUENCE {
   inUse [0] IMPLICIT BOOLEAN,
   listOfRequestTypeDescriptions [1] IMPLICIT SEQUENCE OF TypeDescription,
   listOfResponseTypeDescriptions [2] IMPLICIT SEQUENCE OF TypeDescription,
   programInvocation [3] IMPLICIT Identifier OPTIONAL
}

ExchangeData-Response ::= SEQUENCE {
   listOfResponseData [0] IMPLICIT SEQUENCE OF Data
}

ConfirmedServiceResponse ::= CHOICE {
   status [0] IMPLICIT Status-Response,
   getNameList [1] IMPLICIT GetNameList-Response,
   identify [2] IMPLICIT Identify-Response,
   rename [3] IMPLICIT Rename-Response,
   read [4] IMPLICIT Read-Response,
   write [5] IMPLICIT Write-Response,
   getVariableAccessAttributes [6] IMPLICIT GetVariableAccessAttributes-Response,
   defineNamedVariable [7] IMPLICIT DefineNamedVariable-Response,
   defineScatteredAccess [8] IMPLICIT DefineScatteredAccess-Response,
   getScatteredAccessAttributes [9] IMPLICIT GetScatteredAccessAttributes-Response,
   deleteVariableAccess [10] IMPLICIT DeleteVariableAccess-Response,
   defineNamedVariableList [11] IMPLICIT DefineNamedVariableList-Response,
   getNamedVariableListAttributes [12] IMPLICIT GetNamedVariableListAttributes-Response,
   deleteNamedVariableList [13] IMPLICIT DeleteNamedVariableList-Response,
   defineNamedType [14] IMPLICIT DefineNamedType-Response,
   getNamedTypeAttributes [15] IMPLICIT GetNamedTypeAttributes-Response,
   deleteNamedType [16] IMPLICIT DeleteNamedType-Response,
   input [17] IMPLICIT Input-Response,
   output [18] IMPLICIT Output-Response,
   takeControl [19] TakeControl-Response,
   relinquishControl [20] IMPLICIT RelinquishControl-Response,
   defineSemaphore [21] IMPLICIT DefineSemaphore-Response,
   deleteSemaphore [22] IMPLICIT DeleteSemaphore-Response,
   reportSemaphoreStatus [23] IMPLICIT ReportSemaphoreStatus-Response,
   reportPoolSemaphoreStatus [24] IMPLICIT ReportPoolSemaphoreStatus-Response,
   reportSemaphoreEntryStatus [25] IMPLICIT ReportSemaphoreEntryStatus-Response,
   initiateDownloadSequence [26] IMPLICIT InitiateDownloadSequence-Response,
   downloadSegment [27] IMPLICIT DownloadSegment-Response,
   terminateDownloadSequence [28] IMPLICIT TerminateDownloadSequence-Response,
   initiateUploadSequence [29] IMPLICIT InitiateUploadSequence-Response,
   uploadSegment [30] IMPLICIT UploadSegment-Response,
   terminateUploadSequence [31] IMPLICIT TerminateUploadSequence-Response,
   requestDomainDownload [32] IMPLICIT RequestDomainDownload-Response,
   requestDomainUpload [33] IMPLICIT RequestDomainUpload-Response,
   loadDomainContent [34] IMPLICIT LoadDomainContent-Response,
   storeDomainContent [35] IMPLICIT StoreDomainContent-Response,
   deleteDomain [36] IMPLICIT DeleteDomain-Response,
   getDomainAttributes [37] IMPLICIT GetDomainAttributes-Response,
   createProgramInvocation [38] IMPLICIT CreateProgramInvocation-Response,
   deleteProgramInvocation [39] IMPLICIT DeleteProgramInvocation-Response,
   start [40] IMPLICIT Start-Response,
   stop [41] IMPLICIT Stop-Response,
   resume [42] IMPLICIT Resume-Response,
   reset [43] IMPLICIT Reset-Response,
   kill [44] IMPLICIT Kill-Response,
   getProgramInvocationAttributes [45] IMPLICIT GetProgramInvocationAttributes-Response,
   obtainFile [46] IMPLICIT ObtainFile-Response,
   defineEventCondition [47] IMPLICIT DefineEventCondition-Response,
   deleteEventCondition [48] IMPLICIT DeleteEventCondition-Response,
   getEventConditionAttributes [49] IMPLICIT GetEventConditionAttributes-Response,
      reportEventConditionStatus [50] IMPLICIT ReportEventConditionStatus-Response,
   alterEventConditionMonitoring [51] IMPLICIT AlterEventConditionMonitoring-Response,
   triggerEvent [52] IMPLICIT TriggerEvent-Response,
   defineEventAction [53] IMPLICIT DefineEventAction-Response,
   deleteEventAction [54] IMPLICIT DeleteEventAction-Response,
   getEventActionAttributes [55] IMPLICIT GetEventActionAttributes-Response,
   reportEventActionStatus [56] IMPLICIT ReportEventActionStatus-Response,
   defineEventEnrollment [57] IMPLICIT DefineEventEnrollment-Response,
   deleteEventEnrollment [58] IMPLICIT DeleteEventEnrollment-Response,
   alterEventEnrollment [59] IMPLICIT AlterEventEnrollment-Response,
   reportEventEnrollmentStatus [60] IMPLICIT ReportEventEnrollmentStatus-Response,
   getEventEnrollmentAttributes [61] IMPLICIT GetEventEnrollmentAttributes-Response,
   acknowledgeEventNotification [62] IMPLICIT AcknowledgeEventNotification-Response,
   getAlarmSummary [63] IMPLICIT GetAlarmSummary-Response,
   getAlarmEnrollmentSummary [64] IMPLICIT GetAlarmEnrollmentSummary-Response,
   readJournal [65] IMPLICIT ReadJournal-Response,
   writeJournal [66] IMPLICIT WriteJournal-Response,
   initializeJournal [67] IMPLICIT InitializeJournal-Response,
   reportJournalStatus [68] IMPLICIT ReportJournalStatus-Response,
   createJournal [69] IMPLICIT CreateJournal-Response,
   deleteJournal [70] IMPLICIT DeleteJournal-Response,
   getCapabilityList [71] IMPLICIT GetCapabilityList-Response,
   fileOpen [72] IMPLICIT FileOpen-Response,
   fileRead [73] IMPLICIT FileRead-Response,
   fileClose [74] IMPLICIT FileClose-Response,
   fileRename [75] IMPLICIT FileRename-Response,
   fileDelete [76] IMPLICIT FileDelete-Response,
   fileDirectory [77] IMPLICIT FileDirectory-Response,
   getDataExchangeAttributes [80] GetDataExchangeAttributes-Response,
   exchangeData [81] IMPLICIT ExchangeData-Response
}

Confirmed-ResponsePDU ::= SEQUENCE {
   invokeID Unsigned32,
   service ConfirmedServiceResponse
}

Confirmed-ErrorPDU ::= SEQUENCE {
   invokeID [0] IMPLICIT Unsigned32,
   modifierPosition [1] IMPLICIT Unsigned32 OPTIONAL,
   serviceError [2] IMPLICIT ServiceError
}

InformationReport ::= SEQUENCE {
   variableAccessSpecification VariableAccessSpecification,
   listOfAccessResult [0] IMPLICIT SEQUENCE OF AccessResult
}

EventNotification ::= SEQUENCE {
   eventEnrollmentName [0] ObjectName,
   eventConditionName [1] ObjectName,
   severity [2] IMPLICIT Severity,
   currentState [3] IMPLICIT EC-State OPTIONAL,
   transitionTime [4] EventTime,
   notificationLost [6] IMPLICIT BOOLEAN DEFAULT FALSE,
   alarmAcknowledgmentRule [7] IMPLICIT AlarmAckRule OPTIONAL,
   actionResult [8] IMPLICIT SEQUENCE {
      eventActionName ObjectName,
      successOrFailure CHOICE {
         success [0]  ConfirmedServiceResponse,
         failure [1] ServiceError
      }
   } OPTIONAL
}

UnconfirmedService ::= CHOICE {
   informationReport [0] IMPLICIT InformationReport,
   unsolicitedStatus [1] IMPLICIT UnsolicitedStatus,
   eventNotification [2] IMPLICIT EventNotification
}

Unconfirmed-PDU ::= SEQUENCE {
   service UnconfirmedService
}

RejectPDU ::= SEQUENCE {
   originalInvokeID [0] IMPLICIT Unsigned32 OPTIONAL,
   rejectReason CHOICE {
      confirmed-requestPDU [1] IMPLICIT INTEGER {
         other(0),
         unrecognized-service(1),
         unrecognized-modifier(2),
         invalid-invokeID(3),
         invalid-argument(4),
         invalid-modifier(5),
         max-serv-outstanding-exceeded(6),
         max-recursion-exceeded(8),
         value-out-of-range(9)
      } (0..9),
      confirmed-responsePDU [2] IMPLICIT INTEGER {
         other(0),
         unrecognized-service(1),
         invalid-invokeID(2),
         invalid-result(3),
         max-recursion-exceeded(5),
         value-out-of-range(6)
      } (0..6),
      confirmed-errorPDU [3] IMPLICIT INTEGER {
         other(0),
         unrecognized-service(1),
         invalid-invokeID(2),
         invalid-serviceError(3),
         value-out-of-range(4)
      } (0..4),
      unconfirmedPDU [4] IMPLICIT INTEGER {
         other(0),
         unrecognized-service(1),
         invalid-argument(2),
         max-recursion-exceeded(3),
         value-out-of-range(4)
      } (0..4),
      pdu-error [5] IMPLICIT INTEGER {
         unknown-pdu-type(0),
         invalid-pdu(1),
         illegal-acse-mapping(2)
      } (0..2),
      cancel-requestPDU [6] IMPLICIT INTEGER {
         other(0),
         invalid-invokeID(1)
      } (0..1),
      cancel-responsePDU [7] IMPLICIT INTEGER {
         other(0),
         invalid-invokeID(1)
      } (0..1),
      cancel-errorPDU [8] IMPLICIT INTEGER {
         other(0),
         invalid-invokeID(1),
         invalid-serviceError(2),
         value-out-of-range(3)
      } (0..3),
      conclude-requestPDU [9] IMPLICIT INTEGER {
         other(0),
         invalid-argument(1)
      } (0..1),
      conclude-responsePDU [10] IMPLICIT INTEGER {
         other(0),
         invalid-result(1)
      } (0..1),
      conclude-errorPDU [11] IMPLICIT INTEGER {
         other(0),
         invalid-serviceError(1),
         value-out-of-range(2)
      } (0..2)
   }
}

Cancel-ErrorPDU ::= SEQUENCE {
   originalInvokeID [0] IMPLICIT Unsigned32,
   serviceError [1] IMPLICIT ServiceError
}

Initiate-RequestPDU ::= SEQUENCE {
   localDetailCalling [0] IMPLICIT Integer32 OPTIONAL,
   proposedMaxServOutstandingCalling [1] IMPLICIT Integer16,
   proposedMaxServOutstandingCalled [2] IMPLICIT Integer16,
   proposedDataStructureNestingLevel [3] IMPLICIT Integer8 OPTIONAL,
   initRequestDetail [4] IMPLICIT SEQUENCE {
      proposedVersionNumber [0] IMPLICIT Integer16,
      proposedParameterCBB [1] IMPLICIT ParameterSupportOptions,
      servicesSupportedCalling [2] IMPLICIT ServiceSupportOptions
   }
}

Initiate-ResponsePDU ::= SEQUENCE {
   localDetailCalled [0] IMPLICIT Integer32 OPTIONAL,
   negotiatedMaxServOutstandingCalling [1] IMPLICIT Integer16,
   negotiatedMaxServOutstandingCalled [2] IMPLICIT Integer16,
   negotiatedDataStructureNestingLevel [3] IMPLICIT Integer8 OPTIONAL,
   initResponseDetail [4] IMPLICIT SEQUENCE {
      negotiatedVersionNumber [0] IMPLICIT Integer16,
      negotiatedParameterCBB [1] IMPLICIT ParameterSupportOptions,
      servicesSupportedCalled [2] IMPLICIT ServiceSupportOptions
   }
}

MMSpdu ::= CHOICE {
   confirmed-RequestPDU [0] IMPLICIT Confirmed-RequestPDU,
   confirmed-ResponsePDU [1] IMPLICIT Confirmed-ResponsePDU,
   confirmed-ErrorPDU [2] IMPLICIT Confirmed-ErrorPDU,
   unconfirmed-PDU [3] IMPLICIT Unconfirmed-PDU,
   rejectPDU [4] IMPLICIT RejectPDU,
   cancel-RequestPDU [5] IMPLICIT Cancel-RequestPDU,
   cancel-ResponsePDU [6] IMPLICIT Cancel-ResponsePDU,
   cancel-ErrorPDU [7] IMPLICIT Cancel-ErrorPDU,
   initiate-RequestPDU [8] IMPLICIT Initiate-RequestPDU,
   initiate-ResponsePDU [9] IMPLICIT Initiate-ResponsePDU,
   initiate-ErrorPDU [10] IMPLICIT Initiate-ErrorPDU,
   conclude-RequestPDU [11] IMPLICIT Conclude-RequestPDU,
   conclude-ResponsePDU [12] IMPLICIT Conclude-ResponsePDU,
   conclude-ErrorPDU [13] IMPLICIT Conclude-ErrorPDU
}

ReconfigureProgramInvocation-Request ::= SEQUENCE {
   oldProgramInvocationName [0] IMPLICIT Identifier,
   newProgramInvocationName [1] IMPLICIT Identifier OPTIONAL,
   domainsToAdd [2] IMPLICIT SEQUENCE OF Identifier,
   domainsToRemove [3] IMPLICIT SEQUENCE OF Identifier
}

Write-Response ::= SEQUENCE OF CHOICE {
   failure [0] IMPLICIT DataAccessError,
   success [1] IMPLICIT NULL
}

-- Value assignments

maxIdentifier INTEGER ::= 32
mms-abstract-syntax-version1 OBJECT IDENTIFIER ::= { iso(1) standard(0) iso9506(9506) part(2) mms-abstract-syntax-version1(1) }

END
